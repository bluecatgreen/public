module openconfig-platform-holder {

  yang-version "1";

  // namespace
  namespace "http://openconfig.net/yang/platform/holder";

  prefix "oc-holder";

  import openconfig-platform { prefix oc-platform; }
  import openconfig-types { prefix oc-types; }
  import openconfig-extensions { prefix oc-ext; }


  // meta
  organization "OpenConfig working group";

  contact
    "OpenConfig working group
    www.openconfig.net";

  description
    "This module defines data related to holder
    OpenConfig platform model.";

  oc-ext:openconfig-version "0.1.1";


  revision "2020-04-06" {
    description
      "Initial revision";
    reference "0.1.0";
  }

  // OpenConfig specific extensions for module metadata.
  oc-ext:regexp-posix;
  oc-ext:catalog-organization "openconfig";
  oc-ext:origin "openconfig";


  augment "/oc-platform:components/oc-platform:component/" +
    "oc-platform:holders/oc-platform:holder" {
    description
      "adding attributes for holder";
    leaf name{
       type string;
    }
    leaf occupying_component{
      type leafref {
                  path  "/oc-platform:components/oc-platform:component/oc-platform:name";
      }
    }
    list connectors {
      key "name";
      leaf name {
            type leafref { 
                  path  "/oc-platform:components/oc-platform:component/oc-platform:connectors/oc-platform:connector/oc-platform:connectorname";
                     }
             }
    }
    list supported_components {
      key "name";
      leaf name {
            type leafref { 
                  path  "/oc-platform:components/oc-platform:component/oc-platform:name";
                     }
             }
    }
  }
}
